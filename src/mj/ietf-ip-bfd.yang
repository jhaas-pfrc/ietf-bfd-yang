module ietf-ip-bfd {
    namespace "urn:ietf:params:xml:ns:yang:bfd:ip";
    prefix "ip-bfd";

    import ietf-bfd {
        prefix "bfd";
    }

    organization "IETF BFD (Bidirectional Forwarding Detection) Working Group";
    contact 
        "WG Web:   <http://tools.ietf.org/wg/bfd/>
         WG List:  <mailto:rtg-bfd@ietf.org>

         WG Chair: ";

    description 
        "YANG Model for IP based BFD sessions.

         Copyright (c) 2014 IETF Trust and the persons identified as
         authors of the code.  All rights reserved.

         Redistribution and use in source and binary forms, with or
         without modification, is permitted pursuant to, and subject
         to the license terms contained in, the Simplified BSD License
         set forth in Section 4.c of the IETF Trust's Legal Provisions
         Relating to IETF Documents
         (http://trustee.ietf.org/license-info).

         This version of this YANG module is part of RFC XXXX; see
         the RFC itself for full legal notices.";

    revision 
        "2014-10-14" {
        description "Initial version";
    }

/*
 * typedefs
 */

/* 
 * configuration 
 */
    augment "/bfd:bfd-config" {
        when "bfd:type = 'ianabfdt:ip'";

        list ip-bfd {
            key "/bfd:bfd-config/bfd:my-discriminator";

            leaf single-hop {
                type boolean;
                default "false";
                description
                    "If enabled, this is a single hop BFD session. That
                     means the BFD session has to terminate on the peer
                     IP interface which is a single hop away.";
            }
            leaf protocol {
                type bits {
                    bit bgp {
                        position 0;
                        description
                            "Border Gateway Protocol";
                    }
                    bit ospf {
                        position 1;
                        description
                            "Open Shortest Path First";
                    }
                    bit isis {
                        position 2;
                        description
                            "Intermediate System to Intermediate System";
                    }
                }
                description
                    "List of protocols that are being monitored by this
                     BFD session.";
            }
        }
    }
}
