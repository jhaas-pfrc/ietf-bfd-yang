module ietf-lsp-bfd {
    namespace "urn:ietf:params:xml:ns:yang:bfd:lsp";
    prefix "lsp-bfd";

    import ietf-bfd {
        prefix "bfd";
    }

    organization "IETF BFD (Bidirectional Forwarding Detection) Working Group";
    contact 
        "WG Web:   <http://tools.ietf.org/wg/bfd/>
         WG List:  <mailto:rtg-bfd@ietf.org>

         WG Chair: ";

    description 
        "YANG Model for LSP based BFD sessions.

         Copyright (c) 2014 IETF Trust and the persons identified as
         authors of the code.  All rights reserved.

         Redistribution and use in source and binary forms, with or
         without modification, is permitted pursuant to, and subject
         to the license terms contained in, the Simplified BSD License
         set forth in Section 4.c of the IETF Trust's Legal Provisions
         Relating to IETF Documents
         (http://trustee.ietf.org/license-info).

         This version of this YANG module is part of RFC XXXX; see
         the RFC itself for full legal notices.";

    revision 
        "2014-10-22" {
        description "Initial version";
    }

/*
 * typedefs
 */

/* 
 * configuration 
 */
    augment "/bfd:bfd-config" {
        when "bfd:type = 'ianabfdt:lsp'";

        list lsp-bfd {
            key "/bfd:bfd-config/bfd:my-discriminator";

            leaf tunnel-id {
                type string;
                description
                    "The tunnel which is being monitored by this
                     BFD session.";
            }
        }
    }
}
