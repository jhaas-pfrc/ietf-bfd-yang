module bfd-ip {
  namespace "urn:ietf:params:xml:ns:yang:bfd-ip";
  prefix "bfd-ip";
   
  import bfd-base {
    prefix "bfd";
  }

  import ietf-inet-types {
    prefix "inet";
  }
  // import ietf-interfaces {
  //   prefix "if";
  // }
  organization "IETF BFD Working Group";

  contact 
    "WG Web:   <http://tools.ietf.org/wg/bfd>
      WG List:  TBD
      WG Chair: Jeff Haas
      WG Chair: Nobo Akiya
      Editor:   Vero + Reshad";

  description "This module contains the YANG definition RFC5881";

  revision 2014-09-08 {
    description "Initial revision.";
  }
  list sessions-ip {
    key "interface dest-address";
    leaf interface {
      type string;
      description "Interface";
    }
    leaf dest-address {
      type inet:ip-address;
      description "Peer address";
    }
    leaf sourcePort {
      type uint16;
      description "Source UDP port";
    }

    uses bfd:baseSessionEntry;

  }

  // augment "/bfd:sessions-base/bfd:sessionEntry" {
  //   //key "interface dest-address";
  //   leaf interface {
  //     type string;
  //   }
  //   leaf dest-address {
  //     type inet:ip-address;
  //   }
  //   leaf sourcePort {
  //     type uint16;
  //   }
  // }

}
