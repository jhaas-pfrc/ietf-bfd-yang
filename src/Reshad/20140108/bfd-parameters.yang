module bfd-parameters {
  namespace "urn:ietf:params:xml:ns:yang:bfd-parms";
  prefix "bfd-parms";
   
  organization "IETF BFD Working Group";

  contact 
    "WG Web:   <http://tools.ietf.org/wg/bfd>
      WG List:  TBD
      WG Chair: Jeff Haas
      WG Chair: Nobo Akiya
      Editor:   Vero + Reshad";

  description 
    "This module contains the YANG definition for BFD parameters as per 
     RFC5881";

  revision 2015-01-06 {
    description "Initial revision.";
  }

  typedef discriminator {
    type uint32 {
      range 1..4294967295;
    }
  }

  typedef diagnostic {    
    type enumeration {
      enum none {
	value 0;
      }
      enum controlExpiry {
	value 1;
      }
      enum echoFailed {
	value 2;
      }
      enum nborDown {
	value 3;
      }
      enum fwdingReset {
	value 4;
      }
      enum pathDown {
	value 5;
      }
      enum concPathDown {
	value 6;
      }
      enum adminDown {
	value 7;
      }
      enum reverseConcPathDown {
	value 8;
      }
    }
  }

  typedef state {    
    type enumeration {
      enum adminDown {
	value 0;
      }
      enum down {
	value 1;
      }
      enum init {
	value 2;
      }
      enum up {
	value 3;
      }
    }
  }

  typedef multiplier {
    type uint8 {
      range 1..255;
    }
  }

  grouping bfd-sh-cfg-parms {
    description "BFD grouping for config parameters";
    
    container bfd-sh-cfg {
      leaf enabled {
        type boolean;
        description "True if BFD is enabled";
      }

      leaf echo-enabled {
        type boolean;
        description "True if echo mode is enabled";
      }

      leaf local-multiplier {
        type multiplier;
      }

      leaf desired-min-tx-interval {
        type uint32;
      }

      leaf required-min-rx-interval {
        type uint32;
      }

      leaf required-min-rx-echo-interval {
        type uint32;
      }
    }
  }
}
