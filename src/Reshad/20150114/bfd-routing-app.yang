module bfd-routing-app {
   namespace "urn:cisco:params:xml:ns:yang:bfdroutingapp";
   // replace with IANA namespace when assigned
   prefix bfd-routing-app;

   //import ietf-inet-types {
   //  prefix "inet";
   //}
   import bfd-parameters {
     prefix "bfd-parms";
   }

   //import ietf-yang-types {
   //  prefix "yang";
   //}

   import ietf-interfaces {
     prefix "if";
   }

   //import ietf-routing {
   //  prefix "rt";
   //}

   organization
     "ACME";
   contact
     "acme@acme.com";

   description
     "Testing BFD grouping (simulating a routing application)";

   revision 2014-02-14 {
     description
       "Initial revision.";
   }

   feature routing-app-bfd {
     description "BFD configuration under routing-app";
   }

   list area {
     description
       "Specify a routing area.";

     key "area-id";

     leaf area-id {
       type union {
	 type uint32;
	 type string;
       }
     }

     uses bfd-parms:bfd-sh-cfg-parms {
       if-feature routing-app-bfd;
     }

     list interface {
       key "interface";
       leaf interface {
         type if:interface-ref;
       }
       uses bfd-parms:bfd-sh-cfg-parms {
	 if-feature routing-app-bfd;
       }
     }

   }
}
