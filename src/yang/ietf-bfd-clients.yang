module ietf-bfd-clients {
  namespace "urn:ietf:params:xml:ns:yang:ietf-bfd-clients";

  prefix "bfd-clients";

  import ietf-bfd-types {
    prefix "bfd-types";
  }

  organization "IETF BFD Working Group";

  contact
    "WG Web:   <http://tools.ietf.org/wg/bfd>
     WG List:  <rtg-bfd@ietf.org>

     Editors:  Reshad Rahman (rrahman@cisco.com),
               Lianshu Zheng (vero.zheng@huawei.com),
               Mahesh Jethanandani (mjethanandani@gmail.com)";

  description
    "This module contains groupings to be used by protocols which are clients
     of BFD.

     Copyright (c) 2017 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision YYYY-MM-DD {
    description "Initial revision.";
    reference "RFC XXXX: A YANG data model for BFD";
  }

  // RFC Ed.: replace XXXX with actual RFC number and remove this
  // note

  grouping bfd-client-base-cfg-parms {
    description
      "BFD grouping which could be used by a protocol which
       is a client of BFD to enable its use of BFD.";

    container bfd-cfg {
      description "BFD configuration";
      leaf enabled {
        type boolean;
        default false;
        description "True if BFD is enabled";
      }
    }
  }

  grouping bfd-client-ext-cfg-parms {
    description
      "BFD grouping which could be used by a protocol which
       is a client of BFD to enable its use of BFD and the BFD
       parameters it desires.";
    container bfd-cfg {
      description "BFD configuration";
      leaf enabled {
       type boolean;
       default false;
       description "True if BFD is enabled";
      }

      uses bfd-types:bfd-grouping-base-cfg-parms;
    }
  }
}
